Attribute VB_Name = "Module1"
Option Explicit

Public Sub bLOCKtABLE()

   Dim oApp As AcadApplication
   Dim oAcadBlocks As AcadBlocks
   Dim oAcadBlock  As AcadBlock
   Dim sName As String
   Dim lCount As Long
'On Error Resume Next
   Set oApp = ThisDrawing.Application
   Set oAcadBlocks = ThisDrawing.Blocks
   For Each oAcadBlock In oAcadBlocks
      sName = oAcadBlock.Name
      lCount = oAcadBlock.Count
      Debug.Print sName, lCount
   Next
    
End Sub

Public Sub EntList()
   Dim oEnt As AcadEntity
   Dim oBlockRef As AcadBlockReference
On Error Resume Next
   For Each oEnt In ThisDrawing.ModelSpace
     Debug.Print oEnt.ObjectName
     Debug.Print oEnt.ColorIndex
     Debug.Print oEnt.GetMyName
     If oEnt.ObjectName = "AcDbBlockReference" Then
      Set oBlockRef = oEnt
       Debug.Print oBlockRef.Name
       Debug.Print oBlockRef.Material
     End If
   Next
End Sub

Public Sub getClip()
 Dim oApp As AcadApplication
   Dim oAcadBlocks As AcadBlocks
   Dim oAcadBlock  As AcadBlock
   Dim oAcadBlockRef  As AcadBlockReference
    Dim oPoint(2) As Double
   Dim sName As String
   Dim lCount As Long
   Dim oMatrix As Variant
 On Error Resume Next
   Set oApp = ThisDrawing.Application
   Dim oObj As AcadObject
   ThisDrawing.Utility.GetEntity oObj, oPoint
   Stop
   Set oAcadBlockRef = oObj
   
 '  oAcadBlockRef.ResetBlock
 ' oAcadBlockRef.TransformBy(
 oAcadBlockRef.TransformBy oMatrix
  
End Sub
